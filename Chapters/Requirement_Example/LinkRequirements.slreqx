# LinkRequirements

## Mambo Requirements: References to Mambo Requirements.docx (Container)
Imported from Microsoft Word

### Low Altitude Stability: The dron... (Functional)
Low Altitude Stability: The drone needs to maintain a stable hover at a minimum height of 1 meter above the ground.

### Flight Time: The drone should be... (Functional)
Flight Time: The drone should be able to fly continuously for at least 10 minutes on a full battery charge.

### Battery Charging Duration: The b... (Functional)
Battery Charging Duration: The battery should be fully charged within 30 minutes using the provided charger.

### Payload Capacity: The drone shou... (Functional)
Payload Capacity: The drone should carry a load of up to 5 grams without a noticeable drop in performance.

### Speed: The drone should be able ... (Functional)
Speed: The drone should be able to fly at a top speed of 18 km/h under normal conditions.

### Wind Stability: The drone should... (Functional)
Wind Stability: The drone should remain stable in wind speeds up to 15 km/h.

### GPS Precision: The drone’s GPS s... (Functional)
GPS Precision: The drone’s GPS should have a positional accuracy within ±2 meters.

### Camera Quality: The built-in cam... (Functional)
Camera Quality: The built-in camera should have a resolution of at least 720p HD.

### Control Distance: The drone shou... (Functional)
Control Distance: The drone should maintain a reliable connection with the controller up to 100 meters.

### Weight: The drone should not exc... (Functional)
Weight: The drone should not exceed a takeoff weight of 63 grams, including the battery and any attachments.

### Stability: The drone should main... (Functional)
Stability: The drone should maintain a level flight with pitch and roll deviations not exceeding ±5 degrees.

### Hover Precision: The drone shoul... (Functional)
Hover Precision: The drone should hover within a 0.5-meter radius from a fixed point without manual control.

### Temperature Range: The drone sho... (Functional)
Temperature Range: The drone should operate reliably within temperatures ranging from -10°C to 40°C.

### Auto Return: The drone should au... (Functional)
Auto Return: The drone should automatically return to its takeoff point if the signal is lost or the battery is critically low.

### Obstacle Avoidance: The drone sh... (Functional)
Obstacle Avoidance: The drone should detect and avoid obstacles within a range of 1 meter.

### Flight Modes: The drone should o... (Functional)
Flight Modes: The drone should offer at least three flight modes: beginner, intermediate, and expert, each with varying levels of automated control.

### Battery Indicator: The drone sho... (Functional)
Battery Indicator: The drone should have an LED indicator or app notification for battery levels, alerting at 20% remaining.

### FPV Support: The drone should su... (Functional)
FPV Support: The drone should support First Person View (FPV) via a compatible smartphone app, with a latency of less than 200ms.

### Firmware Updates: The drone shou... (Functional)
Firmware Updates: The drone should support firmware updates via USB or Wi-Fi to ensure access to the latest features and fixes.
